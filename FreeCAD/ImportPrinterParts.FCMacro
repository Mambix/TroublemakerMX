# -*- coding: utf-8 -*-

# Macro Begin: ImportPrinterParts.FCMacro +++++++++++++++++++++++++++++++++++++++++++++++++
import FreeCAD
import Part
import Mesh

# filePath = u"D:/GIT/gitHub.com/mambix/TroublemakerMX/stl/"
filePath = u"/home/dlednik/GIT/TroublemakerMX/stl/"

def addCylinder(id, label, radius, height, placement, rotation):
	App.ActiveDocument.addObject("Part::Cylinder",id)
	App.ActiveDocument.ActiveObject.Label = label
	App.ActiveDocument.recompute()
	FreeCAD.getDocument("Unnamed").getObject(id).Radius = radius
	FreeCAD.getDocument("Unnamed").getObject(id).Height = height
	FreeCAD.getDocument("Unnamed").getObject(id).Placement = App.Placement(placement,rotation)

def addSTL(file, label, placement, rotation, color=None):
	Mesh.insert(u"{}{}.stl".format(filePath,file),"Unnamed")
	App.ActiveDocument.ActiveObject.Placement = App.Placement(placement,rotation)
	App.ActiveDocument.ActiveObject.Label = label
	if color is not None:
		FreeCADGui.getDocument("Unnamed").getObject(file).ShapeColor = color

addCylinder("Cylinder1", "X-Right", '4 mm', '409 mm', App.Vector(177,205,427), App.Rotation(App.Vector(1,0,0),90))
addCylinder("Cylinder2", "X-Left", '4 mm', '409 mm', App.Vector(-176,205,427), App.Rotation(App.Vector(1,0,0),90))
addCylinder("Cylinder3", "Y-Back", '4 mm', '410 mm', App.Vector(-205,156.5,445), App.Rotation(App.Vector(0,1,0),90))
addCylinder("Cylinder4", "Y-Front", '4 mm', '410 mm', App.Vector(-205,-182,445), App.Rotation(App.Vector(0,1,0),90))
addCylinder("Cylinder5", "Z-Right", '6 mm', '410 mm', App.Vector(96,178,74), App.Rotation(App.Vector(0,0,1),90))
addCylinder("Cylinder6", "Z-Left", '6 mm', '410 mm', App.Vector(-64,178,74), App.Rotation(App.Vector(0,0,1),90))

addCylinder("Cylinder7", "X-Hot", '3 mm', '309 mm', App.Vector(0,142,443), App.Rotation(App.Vector(1,0,0),90))
addCylinder("Cylinder8", "Y-Hot", '3 mm', '323 mm', App.Vector(-162,0,429), App.Rotation(App.Vector(0,1,0),90))

addSTL(u"Carrige #2","X-Carrige-Back", App.Vector(0,156.5,445), App.Rotation(App.Vector(1,0,0),180))
addSTL(u"Carrige #2 - 180","X-Carrige-Front", App.Vector(0,-182,445), App.Rotation(App.Vector(1,0,0),180))

addSTL(u"Carrige #2","Y-Carrige-Left", App.Vector(-177,0,427), App.Rotation(App.Vector(0,0,1),-90))
addSTL(u"Carrige #2","Y-Carrige-Right", App.Vector(176,0,427), App.Rotation(App.Vector(0,0,1),90))

addSTL(u"Motor_NEMA17","X-Motor", App.Vector(176,262,427), App.Rotation(App.Vector(1,0,0),90))
addSTL(u"Motor_NEMA17","Y-Motor", App.Vector(-262,156.5,445), App.Rotation(App.Vector(0,1,0),90))
addSTL(u"Motor_NEMA17","Z-Motor", App.Vector(16,178,57), App.Rotation(App.Vector(0,0,1),0))

addSTL(u"movedHE_TOP","HE-TOP", App.Vector(0,0,436), App.Rotation(App.Vector(0,0,1),0))
addSTL(u"movedHE_BOTTOM","HE-BOTTOM", App.Vector(0,0,436), App.Rotation(App.Vector(0,0,1),0))
addSTL(u"movedHE_FRONT","HE-FRONT", App.Vector(0,0,436), App.Rotation(App.Vector(0,0,1),0), (1.00,0.67,0.00))
addSTL(u"movedHE_BACK","HE-BACK", App.Vector(0,0,436), App.Rotation(App.Vector(0,0,1),0), (1.00,0.67,0.00))
addSTL(u"movedHE_LEFT","HE-LEFT", App.Vector(0,0,436), App.Rotation(App.Vector(0,0,1),0), (1.00,0.67,0.00))
addSTL(u"movedHE_RIGHT","HE-RIGHT", App.Vector(0,0,436), App.Rotation(App.Vector(0,0,1),0), (1.00,0.67,0.00))

addSTL(u"movedTABLE","TABLE", App.Vector(0,0,0), App.Rotation(App.Vector(0,0,1),0))
# Macro End: ImportPrinterParts.FCMacro +++++++++++++++++++++++++++++++++++++++++++++++++
