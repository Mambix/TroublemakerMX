# -*- coding: utf-8 -*-

# Macro Begin: LoadPrinter.FCMacro +++++++++++++++++++++++++++++++++++++++++++++++++
import FreeCAD
import Mesh

# filePath = u"D:/GIT/gitHub.com/mambix/TroublemakerMX/stl/"
filePath = u"/home/dlednik/GIT/TroublemakerMX/stl/"


App.newDocument("Unnamed")
#App.setActiveDocument("Unnamed")
#App.ActiveDocument=App.getDocument("Unnamed")
#Gui.ActiveDocument=Gui.getDocument("Unnamed")
#Gui.activateWorkbench("PartWorkbench")
Mesh.insert(filePath + u"movedDESNO.stl","Unnamed")
#Gui.SendMsgToActiveView("ViewFit")
Mesh.insert(filePath + u"movedDOL.stl","Unnamed")
#Gui.SendMsgToActiveView("ViewFit")
Mesh.insert(filePath + u"movedGOR.stl","Unnamed")
#Gui.SendMsgToActiveView("ViewFit")
Mesh.insert(filePath + u"movedLEVO.stl","Unnamed")
#Gui.SendMsgToActiveView("ViewFit")
Mesh.insert(filePath + u"movedSPREDAJ.stl","Unnamed")
#Gui.SendMsgToActiveView("ViewFit")
Mesh.insert(filePath + u"movedZADAJ.stl","Unnamed")
#Gui.SendMsgToActiveView("ViewFit")
FreeCADGui.getDocument("Unnamed").getObject("movedDOL").ShapeColor = (0.00,0.00,1.00)
FreeCADGui.getDocument("Unnamed").getObject("movedGOR").ShapeColor = (0.00,0.00,1.00)
FreeCADGui.getDocument("Unnamed").getObject("movedLEVO").ShapeColor = (0.00,0.67,0.00)
FreeCADGui.getDocument("Unnamed").getObject("movedDESNO").ShapeColor = (0.00,0.67,0.00)
FreeCADGui.getDocument("Unnamed").getObject("movedSPREDAJ").ShapeColor = (1.00,0.33,0.00)
FreeCADGui.getDocument("Unnamed").getObject("movedZADAJ").ShapeColor = (1.00,0.33,0.00)
# Macro End: LoadPrinter.FCMacro +++++++++++++++++++++++++++++++++++++++++++++++++
